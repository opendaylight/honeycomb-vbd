module subinterface-span {
  yang-version 1;
  namespace "urn:opendaylight:params:xml:ns:yang:subinterface-span";
  prefix "subif-span";

  revision "2017-05-10" {
    description
      "Initialial revision that adds support for mirroring interfaces on subinterfaces.
       Vpp implementation allows/implements only two cases:
        - Src: interface |Dst: interface - covered in v3po.yang
        - Src: interface |Dst: subinterface - covered by this model";
  }

  revision "2017-06-07" {
    description "Eliminated config leafrefs in operational tree";
  }

  import ietf-interfaces {
      prefix "if";
  }

  import v3po {
    prefix "v3po";
  }

  import vpp-vlan {
    prefix "vpp-vlan";
  }

  import yang-ext {
    prefix "ext";
  }

  augment /if:interfaces/if:interface/vpp-vlan:sub-interfaces/vpp-vlan:sub-interface {
      ext:augment-identifier "vpp-subinterface-span-augmentation";

      container span {
        uses v3po:span-attributes;
      }
  }

  augment /if:interfaces-state/if:interface/vpp-vlan:sub-interfaces/vpp-vlan:sub-interface {
      ext:augment-identifier "vpp-subinterface-span-state-augmentation";
      container span-state {
        uses v3po:span-state-attributes;
      }
  }
}
