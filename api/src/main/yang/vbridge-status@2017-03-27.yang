module vbridge-status {
   yang-version 1;
   namespace "urn:opendaylight:params:xml:ns:yang:vbridge:status";
   prefix "vbridge-status";

   import v3po {
      prefix v3po;
      revision-date "2017-06-07";
   }

   import yang-ext {
      prefix ext;
      revision-date "2013-07-09";
   }

   revision "2017-03-27" {
        description
        "Revision changes:
         - Changing augmentation to support latest revision of v3po";
      }

   revision "2016-10-05" {
     description
     "Initial revision of bridge domain completion status.";
   }

   grouping bridge-domain-status-fields {
      description "Support fields for bridge domain";

      leaf "bridge-domain-status" {
      description
         "Augments vpp-state in OPER with bridge domain status";
      config false;
         type enumeration {
            enum stopped;
            enum starting;
            enum started;
            enum failed;
         }
      }
   }

   augment "/v3po:bridge-domains-state/v3po:bridge-domain" {
      ext:augment-identifier "bridge-domain-status-augmentation";
      uses bridge-domain-status-fields;
   }
}
