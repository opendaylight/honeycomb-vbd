module vlan-tunnel {
    // vi: set et smarttab sw=4 tabstop=4:

    yang-version 1;
    namespace "urn:opendaylight:params:xml:ns:yang:vbridge:tunnel:vlan";
    prefix "vbridge-tunnel-vlan";

    organization "Cisco Systems, Inc.";

    contact "Tyler Levine <tylevine@cisco.com>";

    description
        "Copyright (c) 2015 Cisco and/or its affiliates.

        Licensed under the Apache License, Version 2.0 (the \"License\");
        you may not use this file except in compliance with the License.
        You may obtain a copy of the License at:

            http://www.apache.org/licenses/LICENSE-2.0

        Unless required by applicable law or agreed to in writing, software
        distributed under the License is distributed on an \"AS IS\" BASIS,
        WITHOUT WARRANTIES OR CONDITIONS OF ANY KIND, either express or implied.
        See the License for the specific language governing permissions and
        limitations under the License.";

    revision "2016-04-29" {
        description "Initial cut";
    }

    import network-topology { prefix nt; revision-date 2013-10-21; }
    import v3po {
        prefix "v3po";
        revision-date "2016-12-14";
    }
    import yang-ext { prefix ext; revision-date "2013-07-09"; }
    import vbridge-topology { prefix vbd; }
    import opendaylight-l2-types { prefix "l2-types"; }
    import vpp-vlan {
        prefix "vpp-vlan";
        revision-date "2016-12-14";
    }

    identity tunnel-type-vlan {
        description "VLAN provider network";
        base vbd:tunnel-type;
    }

    augment "/nt:network-topology/nt:topology/vbd:tunnel-parameters"  {
        ext:augment-identifier "topology-vbridge-vlan-network-parameters-augment";
        when "./nt:topology-types/vbridge-topology";

        case vlan-network-parameters {
            leaf vlan-id {
                description "VLAN tag to use on this provider network";
                type l2-types:vlan-id;
            }
            leaf vlan-type {
                description "Type of VLAN tag to use on this provider network";
                type vpp-vlan:vlan-type;
            }
        }
    }

    augment "/nt:network-topology/nt:topology/nt:node" {
        ext:augment-identifier "node-vbridge-vlan-augment";
        when "../nt:topology-types/vbridge-topology";

        leaf super-interface {
            description "Super interface to use for VLAN subinterface. This is an interface residing on the remote node.
                         This field should be set to the name of the remote interface, such that it can be used as a key
                         into the remote node's ietf-interfaces data tree.";
            type string;
        }

    }
}
