module vpp-classifier {
  yang-version 1;
  namespace "urn:opendaylight:params:xml:ns:yang:vpp:classifier";
  prefix "vpp-classifier";

  revision "2015-06-03" {
    description
    "Initial revision of model for VPP packet classifier.";
  }

  import ietf-yang-types {
    prefix "yang";
  }

  typedef classify-table-ref {
    type leafref {
      path "/vpp-classifier:vpp-classifier/classify-table/name";
    }
    description
      "This type is used by data models that need to reference
       configured classify tables.";
  }

  typedef vpp-node-index {
    type uint32; // 0 deny, ~0 permit, TODO other values (pointers to VPP node) possible
  }

  // TODO add restrictions on leaf values
  grouping classify-session-attributes {
    leaf hit_next_index {
      type vpp-node-index;
      mandatory true;
    }
    leaf opaque_index {
      type uint32;
    }
    leaf advance {
      type int32;
      default 0;
    }
  }

  grouping classify-table-attributes {
    leaf nbuckets {
      mandatory true;
      type uint32;
    }
    leaf memory_size {
      mandatory true;
      type uint32;
    }
    leaf skip_n_vectors {
      mandatory true;
      type uint32;
    }
    leaf match_n_vectors {
      mandatory true;
      type uint32;
    }
    leaf next_table {
      type string;
    }
    leaf miss_next_index {
      mandatory true;
      type vpp-node-index;
    }
    leaf mask {
      type yang:hex-string;
      mandatory true;
    }
    leaf active_sessions {
      type uint32;
      mandatory true;
      config false;
    }

    list classify-session {
      key "match";

      leaf match {
        type yang:hex-string;
      }

      uses classify-session-attributes;
    }
  }

  container vpp-classifier {
    list classify-table {
      key "name";

      leaf name {
        type string;
      }

      uses classify-table-attributes;
    }
  }

}
