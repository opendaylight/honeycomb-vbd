module vxlan-tunnel {
    // vi: set et smarttab sw=4 tabstop=4:

    yang-version 1;
    namespace "urn:opendaylight:params:xml:ns:yang:vbridge:tunnel:vxlan";
    prefix "vbridge-tunnel-vxlan";

    organization "Cisco Systems, Inc.";

    contact "Tyler Levine <tylevine@cisco.com>";

    description
        "Copyright (c) 2015 Cisco and/or its affiliates.

        Licensed under the Apache License, Version 2.0 (the \"License\");
        you may not use this file except in compliance with the License.
        You may obtain a copy of the License at:

            http://www.apache.org/licenses/LICENSE-2.0

        Unless required by applicable law or agreed to in writing, software
        distributed under the License is distributed on an \"AS IS\" BASIS,
        WITHOUT WARRANTIES OR CONDITIONS OF ANY KIND, either express or implied.
        See the License for the specific language governing permissions and
        limitations under the License.";

    revision "2016-04-29" {
        description "Initial cut";
    }

    import network-topology { prefix nt; revision-date 2013-10-21; }
    import v3po { prefix "v3po"; }
    import yang-ext { prefix ext; revision-date "2013-07-09"; }
    import vbridge-topology { prefix vbd; }

    identity tunnel-type-vxlan {
        description "VXLAN tunneling";
        base vbd:tunnel-type;
    }

    augment "/nt:network-topology/nt:topology/vbd:tunnel-parameters"  {
        ext:augment-identifier "topology-vbridge-vxlan-tunnel-parameters-augment";
        when "./nt:topology-types/vbridge-topology";

        case vxlan-tunnel-parameters {
            leaf vni {
                description "VNI to use for encap";
                type v3po:vxlan-vni;
            }
        }
    }
}
